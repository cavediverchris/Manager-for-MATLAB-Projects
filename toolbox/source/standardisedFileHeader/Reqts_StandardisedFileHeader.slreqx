# Reqts_StandardisedFileHeader
This is the requirements specification module for the function to create a Standardised File Header

## #1: File Name (Functional)
The utility shall request a filename from the user.

## #2: Title Line (Functional)
The first line of the file shall be the title.
The title line will be in the format:
%% Short title

## #3: Create file (Functional)
The utility shall create a new file with a filename as previously specified.

## #4: Camel Case (Functional)
The name shall be reformatted to be in camel case

## #5: Path (Functional)
The utility shall request the destination folder
